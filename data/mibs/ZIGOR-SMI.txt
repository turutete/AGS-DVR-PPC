ZIGOR-SMI DEFINITIONS ::= BEGIN

IMPORTS
	MODULE-IDENTITY,
	OBJECT-IDENTITY,
	enterprises
		FROM SNMPv2-SMI;

zigor MODULE-IDENTITY
	LAST-UPDATED "201003071130Z"
	ORGANIZATION "Corporacion Zigor, S.A."
	CONTACT-INFO
		"	Corporacion Zigor, S.A.
			Depto. I+D

		Postal: C/ Portal de Gamarra, 28
			C.P 01013 Vitoria-Gasteiz , Alava
			(Spain)
	
		Tel:	+34 (945) 214 600

		E-mail:	zigor@zigor.com"
	DESCRIPTION
		"The Structure of Management Information for the
		Zigor enterprise."
	::= { enterprises 4576 }	-- assigned by IANA

zigorProducts OBJECT-IDENTITY
	STATUS current
	DESCRIPTION
		"zigorProducts is the root OBJECT IDENTIFIER from
		which sysObjectID values are assigned.  Actual
		values are defined in ZIGOR-PRODUCTS-MIB."
	::= { zigor 1 }

-- Note that zigor.2 is reserved

zigorMgmt OBJECT-IDENTITY
	STATUS current
	DESCRIPTION
		"zigorMgmt is the main subtree for new mib development."
	::= { zigor 3 }

zigorExperiment  OBJECT-IDENTITY
	STATUS current
	DESCRIPTION
		"zigorExperiment provides a root object identifier
		from which experimental mibs may be temporarily
		based.  mibs are typicially based here if they
		fall in one of two categories
		1) are IETF work-in-process mibs which have not
		been assigned a permanent object identifier by
		the IANA.
		2) are zigor work-in-process which has not been
		assigned a permanent object identifier by the
		zigor assigned number authority, typicially because
		the mib is not ready for deployment.

		NOTE WELL:  support for mibs in the zigorExperiment
		subtree will be deleted when a permanent object
		identifier assignment is made."
	::= { zigor 4 }

zigorModules OBJECT-IDENTITY
	STATUS current
	DESCRIPTION
		"zigorModules provides a root object identifier
		from which MODULE-IDENTITY values may be assigned."
	::= { zigor 5 }

END
